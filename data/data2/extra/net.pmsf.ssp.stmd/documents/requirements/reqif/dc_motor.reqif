# Specification Title

# Specification: Specification Document
- Description: Requirements Document

## R1 (Headline Type)
Model requirements

### M_01 (Requirement Type)
The model of the DC-Motor must contain exaxctly two submodels: A submodel for the electro-magnetic part (further referenced as „electrical submodel“) and a submodel for the mechanical part.
- Type: functional
- Category: model
- Customer: Van.ThanhLe@setlabs.de
- Creator: Maurizio.Ahmann@setlabs.de
- Owner: Maurizio.Ahmann@setlabs.de
- State: defined
- Date: 2022-09-16T02:29:00.000+02:00

### M_02 (Requirement Type)
The electrical submodel must model the torque generation, according to the principle of the permanent magnet DC-Motor with part number XY12346.
- Type: functional
- Category: model
- Customer: Van.ThanhLe@setlabs.de
- Creator: Maurizio.Ahmann@setlabs.de
- Owner: Maurizio.Ahmann@setlabs.de
- State: defined
- Date: 2022-09-16T13:52:00.000+02:00

### M_03 (Requirement Type)
The electrical submodel must have the source voltage as input.
- Type: functional
- Category: model
- Customer: Van.ThanhLe@setlabs.de
- Creator: Maurizio.Ahmann@setlabs.de
- Owner: Maurizio.Ahmann@setlabs.de
- State: defined
- Date: 2022-09-16T13:58:00.000+02:00

### M_04 (Requirement Type)
The electrical submodel must output the drive torque of the motor.
- Type: functional
- Category: model
- Customer: Van.ThanhLe@setlabs.de
- Creator: Maurizio.Ahmann@setlabs.de
- Owner: Maurizio.Ahmann@setlabs.de
- State: defined
- Date: 2022-09-16T14:19:00.000+02:00

### M_05 (Requirement Type)
The electrical submodel is allowed to have further inputs and outputs, if necessary.
- Type: information
- Category: model
- Customer: Van.ThanhLe@setlabs.de
- Creator: Maurizio.Ahmann@setlabs.de
- Owner: Maurizio.Ahmann@setlabs.de
- State: defined
- Date: 2022-09-16T14:22:00.000+02:00

### M_06 (Requirement Type)
The electrical submodel must model copper losses.
- Type: functional
- Category: model
- Customer: Van.ThanhLe@setlabs.de
- Creator: Maurizio.Ahmann@setlabs.de
- Owner: Maurizio.Ahmann@setlabs.de
- State: defined
- Date: 2022-09-19T07:30:00.000+02:00

### M_07 (Requirement Type)
Magnetic losses (hysteris and eddy currents) must be modelled, if they are greater than 10% of copper losses, in terms of power.
- Type: functional
- Category: model
- Customer: Van.ThanhLe@setlabs.de
- Creator: Maurizio.Ahmann@setlabs.de
- Owner: Maurizio.Ahmann@setlabs.de
- State: defined
- Date: 2022-09-19T07:30:00.000+02:00

### M_08 (Requirement Type)
The mechanical submodel must model the kinematics of the DC-Motor with part number XY12346.
- Type: functional
- Category: model
- Customer: Van.ThanhLe@setlabs.de
- Creator: Maurizio.Ahmann@setlabs.de
- Owner: Maurizio.Ahmann@setlabs.de
- State: defined
- Date: 2022-09-19T07:40:00.000+02:00

### M_09 (Requirement Type)
The mechanical submodel must have the drive torque as input.
- Type: functional
- Category: model
- Customer: Van.ThanhLe@setlabs.de
- Creator: Maurizio.Ahmann@setlabs.de
- Owner: Maurizio.Ahmann@setlabs.de
- State: defined
- Date: 2022-09-19T07:41:00.000+02:00

### M_10 (Requirement Type)
The mechanical submodel must model the brush friction.
- Type: functional
- Category: model
- Customer: Van.ThanhLe@setlabs.de
- Creator: Maurizio.Ahmann@setlabs.de
- Owner: Maurizio.Ahmann@setlabs.de
- State: defined
- Date: 2022-09-19T07:44:00.000+02:00

### M_11 (Requirement Type)
The mechanical submodel must model the bearing friction.
- Type: functional
- Category: model
- Customer: Van.ThanhLe@setlabs.de
- Creator: Maurizio.Ahmann@setlabs.de
- Owner: Maurizio.Ahmann@setlabs.de
- State: defined
- Date: 2022-09-19T07:45:00.000+02:00

## R13 (Headline Type)
Parameter requirements

### P_01 (Requirement Type)
The parameters that will be used for model equations must be taken from the data sheet of the DC-Motor with part number XY12346.
- Type: non-functional
- Category: parameter
- Customer: Van.ThanhLe@setlabs.de
- Creator: Maurizio.Ahmann@setlabs.de
- Owner: Maurizio.Ahmann@setlabs.de
- State: defined
- Date: 2022-09-19T08:57:00.000+02:00

### P_02 (Requirement Type)
For the evaluation of the simulation, the parameter values for 0 minutes of operation, as well as the parameter values for 20 minutes operation must be taken into account.
- Type: functional
- Category: parameter
- Customer: Van.ThanhLe@setlabs.de
- Creator: Maurizio.Ahmann@setlabs.de
- Owner: Maurizio.Ahmann@setlabs.de
- State: defined
- Date: 2022-09-19T08:57:00.000+02:00

### P_03 (Requirement Type)
The value of stiction torque parameters can be set to the same value as the parameters of the friction torque.
- Type: information
- Category: parameter
- Customer: Van.ThanhLe@setlabs.de
- Creator: Maurizio.Ahmann@setlabs.de
- Owner: Maurizio.Ahmann@setlabs.de
- State: defined
- Date: 2022-09-19T09:01:00.000+02:00

### P_04 (Requirement Type)
The rotational stiffness of the rotor between the two flanges is assumed to be 91500 Nm/rad (+/- 20% tolerance).
- Type: functional
- Category: parameter
- Customer: Van.ThanhLe@setlabs.de
- Creator: Maurizio.Ahmann@setlabs.de
- Owner: Maurizio.Ahmann@setlabs.de
- State: defined
- Date: 2022-09-19T09:01:00.000+02:00

## R18 (Headline Type)
Environment requirements

### E_01 (Requirement Type)
All submodels must be available as FMUs for Model Exchange (V 2.0x), compiled for Microsoft Windows 10 systems.
- Category: environment
- Type: functional
- Customer: Van.ThanhLe@setlabs.de
- Creator: Maurizio.Ahmann@setlabs.de
- Owner: Maurizio.Ahmann@setlabs.de
- State: defined
- Date: 2022-09-19T08:52:00.000+02:00

## R20 (Headline Type)
Integration requirements

## I_01 (Requirement Type)
The simulation must have only the voltage source as a global input.
- Category: integration
- Type: functional
- Customer: Van.ThanhLe@setlabs.de
- Creator: Maurizio.Ahmann@setlabs.de
- Owner: Maurizio.Ahmann@setlabs.de
- State: defined
- Date: 2022-09-19T08:46:00.000+02:00

## I_02 (Requirement Type)
The voltage comes from the bordnet of the vehicle and can be modelled as a static value.
- Category: integration
- Type: functional
- Customer: Van.ThanhLe@setlabs.de
- Creator: Maurizio.Ahmann@setlabs.de
- Owner: Maurizio.Ahmann@setlabs.de
- State: defined
- Date: 2022-09-19T08:48:00.000+02:00

## I_03 (Requirement Type)
A positive voltage must cause a positive rotational rotor velocity.
- Category: integration
- Type: functional
- Customer: Van.ThanhLe@setlabs.de
- Creator: Maurizio.Ahmann@setlabs.de
- Owner: Maurizio.Ahmann@setlabs.de
- State: defined
- Date: 2022-09-19T08:51:00.000+02:00

## I_04 (Requirement Type)
A positive load torque must cause a negative rotational rotor velocity.
- Category: integration
- Type: functional
- Customer: Van.ThanhLe@setlabs.de
- Creator: Maurizio.Ahmann@setlabs.de
- Owner: Maurizio.Ahmann@setlabs.de
- State: defined
- Date: 2022-09-19T09:06:00.000+02:00

## I_05 (Requirement Type)
The source voltage must cover a range from -48 V to +48 V.
- Category: integration
- Type: functional
- Customer: Van.ThanhLe@setlabs.de
- Creator: Maurizio.Ahmann@setlabs.de
- Owner: Maurizio.Ahmann@setlabs.de
- State: defined
- Date: 2022-09-19T09:08:00.000+02:00

## I_06 (Requirement Type)
The load torque must cover a range from -2 Nm to +2 Nm.
- Category: integration
- Type: functional
- Customer: Van.ThanhLe@setlabs.de
- Creator: Maurizio.Ahmann@setlabs.de
- Owner: Maurizio.Ahmann@setlabs.de
- State: defined
- Date: 2022-09-19T09:09:00.000+02:00

## I_07 (Requirement Type)
The rotational velocity of the motor must cover a range from -2000 rad/s to +2000 rad/s.
- Category: integration
- Type: functional
- Customer: Van.ThanhLe@setlabs.de
- Creator: Maurizio.Ahmann@setlabs.de
- Owner: Maurizio.Ahmann@setlabs.de
- State: defined
- Date: 2022-09-19T09:10:00.000+02:00

## R28 (Headline Type)
Test case requirements

### T_01 (Requirement Type)
For the target simulation, a step response of the source voltage from 0 to 48 V must be evaluated.
- Category: test case
- Type: functional
- Customer: Van.ThanhLe@setlabs.de
- Creator: Maurizio.Ahmann@setlabs.de
- Owner: Maurizio.Ahmann@setlabs.de
- State: defined
- Date: 2022-09-19T08:54:00.000+02:00

### T_02 (Requirement Type)
For the test described in T_01, a constant load torque of 1 Nm must be applied to the DC-Motor.
- Category: test case
- Type: functional
- Customer: Van.ThanhLe@setlabs.de
- Creator: Maurizio.Ahmann@setlabs.de
- Owner: Maurizio.Ahmann@setlabs.de
- State: defined
- Date: 2022-09-19T08:56:00.000+02:00
